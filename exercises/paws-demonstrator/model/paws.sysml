// =========================================================================
// PAWS DEMONSTRATOR — Dog Grooming Service Business Model
// =========================================================================
//
// Cross-domain validation: validates that BusinessModel part defs
// generalise from a coffee shop (immediate retail) and laundry
// (batch processing) to a structurally different service business
// — an appointment-based personal service.
//
// Key structural differences from Cafe and Suds:
//   - Scheduling: appointment-based with variable duration (vs immediate
//     or batch turnaround)
//   - Service subject: the animal, not the paying customer (analogous
//     to GSL where the patient is the service subject)
//   - Pricing: per-appointment with breed/size surcharges
//   - Process shape: sequential single-animal workflow, one groomer
//     per appointment (vs parallel batch processing in Suds)
//   - Governance: general professional duty of care (Animal Welfare
//     Act 2006), not specific regulation like COSHH
//
// Session 44 (19 March 2026): initial business model creation.
//   Stage 3 Phase 1 — third demonstrator domain.
// =========================================================================

package PawsBusinessModel {
    private import ScalarValues::*;
    private import BusinessMetamodelGeneral::ServiceConcept::*;
    private import BusinessMetamodelGeneral::ActivityModel::*;
    private import BusinessMetamodelGeneral::StakeholderModel::*;

    doc /* Paws dog grooming service business model. Instantiates the
         * ServiceConcept and ActivityModel part defs from the main
         * BusinessModel package to validate cross-domain generalisation
         * for appointment-based personal services.
         *
         * Same meta model vocabulary as Cafe and Suds, different
         * values — this is the test of whether the abstractions
         * generalise across three structurally different service types.
         *
         * Notable modelling observation (Session 44): the paying
         * customer (pet owner) is not the service recipient (the
         * animal). Resolved Session 55 with two sibling General BMM
         * concepts: ServiceSubject (the dog) and ServiceParticipant
         * (the pet owner). This parallels the GSL domain where the
         * patient is the service subject but booking/payment may
         * involve others. See: Service Participation Model discussion
         * document (Session 55). */

    // -- Service Concept --------------------------------------

    part pawsValueProposition : ValueProposition {
        attribute :>> propositionName = "Expert, gentle pet grooming";
        ref :>> targetSegment = individualPetOwner;
        attribute :>> description = "Professional grooming tailored to your dog's breed, coat type, and temperament — in a calm, low-stress environment";
        attribute :>> evidenceBasis = "Customer feedback, repeat booking rates, breed-specific training credentials";
        attribute :>> differentiator = "Breed-specific expertise with a focus on animal comfort and welfare";
    }

    part fullGroom : ServiceOffering {
        doc /* Full grooming session — the core offering. Includes
             * bath, blow-dry, full coat trim/style, nail trim, ear
             * clean, and finishing. Duration varies by breed and
             * coat condition: 60–120 minutes. */
        attribute :>> offeringName = "Full groom";
        attribute :>> description = "Complete grooming: bath, dry, coat trim and style, nail trim, ear clean, finishing touches";
        attribute :>> scope = "Check-in, assess coat condition, bathe, dry, clip/scissor to breed standard or owner preference, nail trim, ear clean, finishing spray, handover";
        attribute :>> pricingBasis = "per-appointment with breed/size surcharge";
        attribute :>> estimatedDurationWeeks = 0;
        attribute :>> clinicalPathwayRef = "full-groom-process";
    }

    part washAndTidy : ServiceOffering {
        doc /* Wash and tidy — a lighter service for dogs that need
             * cleaning but not a full restyle. Bath, blow-dry,
             * light trim around eyes/paws/sanitary areas.
             * 30–60 minutes depending on size. */
        attribute :>> offeringName = "Wash and tidy";
        attribute :>> description = "Bath, blow-dry, and light trim around eyes, paws, and sanitary areas";
        attribute :>> scope = "Check-in, bathe, dry, tidy trim (face, feet, sanitary), finishing, handover";
        attribute :>> pricingBasis = "per-appointment with size surcharge";
        attribute :>> estimatedDurationWeeks = 0;
        attribute :>> clinicalPathwayRef = "wash-and-tidy-process";
    }

    part nailTrimAddOn : ServiceOffering {
        doc /* Nail trim as a standalone service or add-on. Quick
             * appointment — 15 minutes. Available as walk-in or
             * booked alongside other services. */
        attribute :>> offeringName = "Nail trim";
        attribute :>> description = "Nail clipping and filing — standalone or add-on to any grooming service";
        attribute :>> scope = "Assess nails, clip to safe length, file smooth, check dewclaws";
        attribute :>> pricingBasis = "fixed price";
        attribute :>> estimatedDurationWeeks = 0;
        attribute :>> clinicalPathwayRef = "nail-trim-process";
    }

    part individualPetOwner : CustomerSegment {
        attribute :>> segmentName = "Individual pet owners";
        attribute :>> description = "Dog owners booking grooming appointments for one or two pets";
        attribute :>> needs = "Reliable, gentle grooming at a fair price with convenient booking";
        attribute :>> acquisitionChannel = "Walk-in, word of mouth, local social media, Google search";
        attribute :>> willingnessToPayIndicator = "medium";
    }

    part regularMultiPetOwner : CustomerSegment {
        doc /* Owners with multiple dogs or who book on a regular
             * schedule (e.g. every 6–8 weeks). Higher lifetime
             * value, predictable demand. May benefit from a
             * loyalty or subscription discount. */
        attribute :>> segmentName = "Regular and multi-pet owners";
        attribute :>> description = "Owners who book regularly or have multiple dogs — loyal, repeat customers";
        attribute :>> needs = "Consistency, familiarity with their dogs, flexible scheduling, multi-pet discounts";
        attribute :>> acquisitionChannel = "Repeat booking, referral, loyalty programme";
        attribute :>> willingnessToPayIndicator = "medium-high";
    }

    part shopWalkIn : Channel {
        attribute :>> channelName = "Shop and walk-in";
        attribute :>> description = "In-person booking and drop-off at the grooming salon";
        attribute :>> channelType = "acquisition and delivery";
        attribute :>> estimatedReach = "local — walking distance or short drive";
        attribute :>> estimatedCostLevel = "low";
        attribute :>> conversionNotes = "High — customer has brought their dog, strong intent";
    }

    part onlineBookingChannel : Channel {
        attribute :>> channelName = "Online booking";
        attribute :>> description = "Website or app for appointment booking, service selection, and breed/size information";
        attribute :>> channelType = "acquisition and service";
        attribute :>> estimatedReach = "local area — service radius";
        attribute :>> estimatedCostLevel = "medium";
        attribute :>> conversionNotes = "Moderate — depends on reviews and visibility in local search";
    }

    // -- Differentiation Claims --------------------------------

    part breedExpertise : DifferentiationClaim {
        attribute :>> claimName = "Breed-specific grooming expertise";
        attribute :>> statement = "Every groom is tailored to your dog's breed standard and coat type — not a one-size-fits-all clip";
        attribute :>> basis = "Groomers trained in breed-specific techniques; reference library of breed grooming standards maintained";
        attribute :>> testability = "Customer satisfaction by breed type; before/after photos; groomer certification records";
    }

    part lowStressEnvironment : DifferentiationClaim {
        attribute :>> claimName = "Low-stress, gentle handling";
        attribute :>> statement = "We prioritise your dog's comfort — calm environment, patient handling, breaks when needed";
        attribute :>> basis = "Appointment spacing allows adequate time; no rush; one dog per groomer at a time; quiet salon design";
        attribute :>> testability = "Customer feedback on dog's demeanour post-groom; repeat booking rates; incident log frequency";
    }

    // -- Service Subject and Participants ---------------------
    //
    // The paying customer (pet owner) is not the service
    // subject (the dog). These two concepts capture the
    // structural distinction that the original Paws model
    // observation identified (Session 44, resolved Session 55).

    part dogSubject : ServiceSubject {
        doc /* The dog: service subject. Receives the grooming.
             * Has independent welfare needs under the Animal
             * Welfare Act 2006. The groomer's professional duty
             * of care is to the dog — if the animal shows signs
             * of distress, grooming must be paused or adapted
             * regardless of the owner's preferences.
             *
             * This is the participation that most directly maps
             * to GSL's patient: an entity with independent needs,
             * independent governance obligations, and a status
             * that is tracked through the service workflow. */
        attribute :>> subjectName = "Dog";
        attribute :>> entityDescription = "Animal — the dog being groomed";
        attribute :>> independentNeeds = "Animal welfare: calm environment, patient handling, breaks when needed, no unnecessary suffering. Breed-specific coat care requirements. Health issues (skin conditions, lumps, parasites) must be observed and reported to owner.";
        attribute :>> conditionNotes = "Assessed at check-in: coat condition, matting, skin issues, temperament, any special instructions from owner";
        attribute :>> statusNotes = "";
    }

    part petOwnerParticipant : ServiceParticipant {
        doc /* The pet owner: customer, payer, and decision-maker.
             * Books the appointment, pays for the service, states
             * grooming preferences, and collects the dog afterward.
             * The owner's preferences may be overridden by the
             * groomer's duty of care to the animal. */
        attribute :>> participantName = "Pet owner";
        attribute :>> participantRole = "customer, payer, decision-maker";
        attribute :>> entityDescription = "Person — the dog's owner or carer";
        attribute :>> relationshipToEngagement = "Commissions and pays for the grooming service. States preferences for grooming style. Collects the dog and receives any observations about health or condition.";
        attribute :>> statusNotes = "";
    }

    // -- Catalogue Entries ------------------------------------
    //
    // Service offerings as catalogue items. Uses the generic
    // BMM CatalogueEntry — no domain-typed specialisation.
    // Same pattern as Suds (design decision P3-D1 from Stage 2).

    part fullGroomCatalogue : CatalogueEntry {
        doc /* Full groom offering as a catalogue entry.
             * Per-appointment pricing with breed/size bands. */
        attribute :>> entryName = "Full Groom";
        attribute :>> itemReference = "fullGroom";
        attribute :>> pricingDescription = "From £35 (small breed) to £65 (large/double-coated breed)";
        attribute :>> availabilityStatus = "active";
        attribute :>> provisionType = "service";
        attribute :>> effectiveDate = "2026-03-19";
        attribute :>> statusNotes = "Core offering — by appointment, typically 60-120 min";
    }

    part washAndTidyCatalogue : CatalogueEntry {
        doc /* Wash and tidy — lighter service, lower price point. */
        attribute :>> entryName = "Wash and Tidy";
        attribute :>> itemReference = "washAndTidy";
        attribute :>> pricingDescription = "From £20 (small breed) to £40 (large breed)";
        attribute :>> availabilityStatus = "active";
        attribute :>> provisionType = "service";
        attribute :>> effectiveDate = "2026-03-19";
        attribute :>> statusNotes = "Lighter grooming option — 30-60 min";
    }

    part nailTrimCatalogue : CatalogueEntry {
        doc /* Nail trim — standalone or add-on. Fixed price. */
        attribute :>> entryName = "Nail Trim";
        attribute :>> itemReference = "nailTrimAddOn";
        attribute :>> pricingDescription = "£10 standalone, £5 as add-on";
        attribute :>> availabilityStatus = "active";
        attribute :>> provisionType = "service";
        attribute :>> effectiveDate = "2026-03-19";
        attribute :>> statusNotes = "Quick service — 15 min. Walk-in or booked.";
    }

    // -- Activity Model ---------------------------------------
    //
    // Eight activity types following the five-category taxonomy.
    // The process shape is sequential, one-animal-at-a-time —
    // fundamentally different from Suds (batch) and Cafe (immediate).

    part checkInAndAssess : ActivityType {
        doc /* Service delivery: intake. Owner drops off dog,
             * groomer assesses coat condition, skin issues,
             * matting, temperament. Confirms service and any
             * special instructions. */
        attribute :>> activityTypeName = "Check-in and assess";
        attribute :>> activityCategory = ActivityCategory::serviceDelivery;
        attribute :>> description = "Greet owner and dog, confirm service booked, assess coat condition, note any skin issues or matting, record special instructions";
        attribute :>> expectedDurationMinutes = 10;
        attribute :>> frequencyNotes = "Per appointment";
    }

    part batheAndDry : ActivityType {
        doc /* Service delivery: washing. Shampoo appropriate to
             * coat type, rinse, conditioning if needed. Blow-dry
             * or cage-dry depending on breed and temperament.
             * Significant duration variation by coat type. */
        attribute :>> activityTypeName = "Bathe and dry";
        attribute :>> activityCategory = ActivityCategory::serviceDelivery;
        attribute :>> description = "Bathe with breed-appropriate shampoo, rinse, condition if needed, blow-dry to appropriate finish";
        attribute :>> expectedDurationMinutes = 30;
        attribute :>> frequencyNotes = "Per grooming appointment (full groom and wash-and-tidy)";
    }

    part clipAndStyle : ActivityType {
        doc /* Service delivery: the main grooming work. Clipping,
             * scissoring, hand-stripping (for wire-coated breeds)
             * to breed standard or owner preference. Highly
             * variable duration: 20 min for a simple clip to
             * 60+ min for a show trim on a double-coated breed. */
        attribute :>> activityTypeName = "Clip and style";
        attribute :>> activityCategory = ActivityCategory::serviceDelivery;
        attribute :>> description = "Clip, scissor, or hand-strip coat to breed standard or owner preference. Includes face, feet, ears, and sanitary areas.";
        attribute :>> expectedDurationMinutes = 45;
        attribute :>> frequencyNotes = "Per full groom appointment. Tidy trim only for wash-and-tidy.";
    }

    part nailTrimActivity : ActivityType {
        doc /* Service delivery: nail care. Clip to safe length,
             * file smooth, check dewclaws. Can be standalone
             * or part of a full groom. */
        attribute :>> activityTypeName = "Nail trim";
        attribute :>> activityCategory = ActivityCategory::serviceDelivery;
        attribute :>> description = "Clip nails to safe length, file smooth, check and trim dewclaws if present";
        attribute :>> expectedDurationMinutes = 10;
        attribute :>> frequencyNotes = "Per appointment — standalone or as part of full groom";
    }

    part finishAndHandover : ActivityType {
        doc /* Service delivery: final step. Finishing spray,
             * bandana or bow if requested. Final quality check.
             * Notify owner, handover, discuss any observations
             * (skin issues, matting, lumps noticed). */
        attribute :>> activityTypeName = "Finish and handover";
        attribute :>> activityCategory = ActivityCategory::serviceDelivery;
        attribute :>> description = "Apply finishing spray, attach bandana/bow, final quality check, notify owner, handover dog, discuss any observations";
        attribute :>> expectedDurationMinutes = 10;
        attribute :>> frequencyNotes = "Per appointment";
    }

    part equipmentCleanAndMaintenance : ActivityType {
        doc /* Service enabling: keeping grooming equipment in good
             * order. Clean and disinfect tables, baths, dryers.
             * Sharpen and oil clipper blades. Check dryer filters. */
        attribute :>> activityTypeName = "Equipment cleaning and maintenance";
        attribute :>> activityCategory = ActivityCategory::serviceEnabling;
        attribute :>> description = "Clean and disinfect grooming tables, baths, and tools. Sharpen clipper blades. Check dryer filters and hoses.";
        attribute :>> expectedDurationMinutes = 20;
        attribute :>> frequencyNotes = "Between appointments (quick clean) and end of day (thorough)";
    }

    part welfareAndSafetyChecks : ActivityType {
        doc /* Governance: periodic checks that animal welfare and
             * workplace safety standards are maintained. First aid
             * kit, incident log review, premises hygiene, safe
             * handling practices. */
        attribute :>> activityTypeName = "Welfare and safety checks";
        attribute :>> activityCategory = ActivityCategory::governance;
        attribute :>> description = "Review incident log, check first aid kit stock, inspect premises hygiene, verify safe handling practices observed";
        attribute :>> expectedDurationMinutes = 15;
        attribute :>> frequencyNotes = "Weekly";
    }

    part bookingAndAdministration : ActivityType {
        doc /* Overhead: managing the appointment book, taking
             * payments, responding to enquiries, managing the
             * online booking system. */
        attribute :>> activityTypeName = "Booking and administration";
        attribute :>> activityCategory = ActivityCategory::overhead;
        attribute :>> description = "Manage appointment diary, process payments, respond to enquiries, update online booking system, daily reconciliation";
        attribute :>> expectedDurationMinutes = 30;
        attribute :>> frequencyNotes = "Daily — distributed throughout the day";
    }

    // -- Granularity policy ------------------------------------

    part serviceDeliveryGranularity : ActivityGranularity {
        doc /* Service delivery is tracked — each appointment's
             * journey through check-in → groom → handover generates
             * observable events per step. */
        attribute :>> businessArea = "Service delivery";
        attribute :>> currentLevel = GranularityLevel::tracked;
        attribute :>> targetLevel = GranularityLevel::tracked;
        attribute :>> migrationNotes = "Tracked via appointment workflow events through all grooming stages";
    }

    part enablingGranularity : ActivityGranularity {
        attribute :>> businessArea = "Service enabling";
        attribute :>> currentLevel = GranularityLevel::category;
        attribute :>> targetLevel = GranularityLevel::category;
        attribute :>> migrationNotes = "Equipment maintenance logged as category-level events between appointments and at end of day";
    }

    part governanceGranularity : ActivityGranularity {
        attribute :>> businessArea = "Governance";
        attribute :>> currentLevel = GranularityLevel::category;
        attribute :>> targetLevel = GranularityLevel::category;
        attribute :>> migrationNotes = "Weekly welfare checks — category level adequate for general duty of care (no specific regulatory audit trail required unlike COSHH)";
    }

    part developmentGranularity : ActivityGranularity {
        attribute :>> businessArea = "Development";
        attribute :>> currentLevel = GranularityLevel::envelope;
        attribute :>> targetLevel = GranularityLevel::envelope;
        attribute :>> migrationNotes = "CPD and breed training — envelope adequate";
    }

    part overheadGranularity : ActivityGranularity {
        attribute :>> businessArea = "Overhead";
        attribute :>> currentLevel = GranularityLevel::envelope;
        attribute :>> targetLevel = GranularityLevel::envelope;
        attribute :>> migrationNotes = "Daily admin — envelope adequate";
    }

    // -- Activity cost allocations ----------------------------

    part groomingLabourCostAllocation : ActivityCostAllocation {
        doc /* Cost allocation for grooming labour. The groomer's
             * time is the primary variable cost — allocated per
             * appointment based on expected duration. */
        ref :>> activityType = clipAndStyle;
        attribute :>> allocationMethod = "labour time allocation";
        attribute :>> estimatedCostPerUnit = 12.50;
        attribute :>> costNotes = "45 min average at £16.50/hr = £12.38, rounded to £12.50. Varies significantly by breed/coat type.";
    }

    part consumablesCostAllocation : ActivityCostAllocation {
        doc /* Cost allocation for grooming consumables: shampoo,
             * conditioner, finishing spray, blade oil, ear cleaner.
             * Allocated per appointment as an average. */
        ref :>> activityType = batheAndDry;
        attribute :>> allocationMethod = "per-appointment average";
        attribute :>> estimatedCostPerUnit = 2.50;
        attribute :>> costNotes = "Shampoo £1.20, conditioner £0.60, finishing spray £0.40, sundries £0.30. Average across sizes.";
    }

    // -- Stakeholder Model ------------------------------------
    //
    // Cross-domain validation: StakeholderModel instantiations for
    // an appointment-based personal service. Session 81.

    part animalWelfareRegulator : StakeholderRelationship {
        doc /* Local authority animal welfare — regulatory oversight
             * for businesses handling animals. */
        attribute :>> stakeholderName = "Local authority (animal welfare)";
        attribute :>> stakeholderDescription = "Regulatory body responsible for animal welfare standards under the Animal Welfare Act 2006.";
        attribute :>> relationshipNature = RelationshipNature::regulatory;
        attribute :>> obligationsInward = "Sets animal welfare standards for businesses handling animals. Investigates complaints.";
        attribute :>> obligationsOutward = "Comply with Animal Welfare Act 2006. Ensure grooming practices do not cause suffering or distress. Cooperate with any investigation.";
        attribute :>> informationExchanged = "Business registration, incident reports if any (outward). Guidance, investigation outcomes (inward).";
        attribute :>> governanceArrangements = "Business licence (if required by local authority). Complaint-driven investigation process.";
        attribute :>> healthIndicators = "No complaints, no investigations, licence current (if applicable).";
        attribute :>> reviewCadence = "As required — primarily complaint-driven. Voluntary annual self-assessment against industry standards.";
    }

    part groomingInsurance : StakeholderRelationship {
        attribute :>> stakeholderName = "Insurance provider";
        attribute :>> stakeholderDescription = "Professional liability and public liability insurance — contractual relationship.";
        attribute :>> relationshipNature = RelationshipNature::contractual;
        attribute :>> obligationsInward = "Provides insurance cover for professional liability, public liability, and damage to animals in care.";
        attribute :>> obligationsOutward = "Pay premiums, maintain safe working practices, report incidents promptly, comply with policy conditions.";
        attribute :>> informationExchanged = "Policy details, incident notifications, renewal documentation.";
        attribute :>> governanceArrangements = "Annual insurance policy. Incident reporting protocol.";
        attribute :>> healthIndicators = "Policy current, claims history, premium trajectory.";
        attribute :>> reviewCadence = "Annual renewal. Immediate notification for incidents.";
    }

    part vetPartnership : CooperativeArrangement {
        doc /* Local vet partnership for pre-grooming health checks
             * — shared responsibility for animal welfare. */
        attribute :>> arrangementName = "Local vet partnership";
        attribute :>> cooperatingEntity = "Local veterinary practice";
        attribute :>> sharedOutcome = "Grooming of dogs with health conditions is safe and informed by veterinary guidance — neither party can ensure this alone";
        attribute :>> responsibilitySplit = "Vet: health assessment, grooming clearance, advice on handling. Paws: grooming delivery, observation during grooming, reporting concerns back to vet.";
        attribute :>> protocolReference = "Informal professional agreement. Referral form for dogs with health conditions.";
        attribute :>> informationSharing = "Paws sends grooming referral form for dogs with known conditions. Vet sends clearance notes and handling advice.";
        attribute :>> disputeResolution = "Professional discussion between groomer and vet. Owner involved in decisions about their animal.";
        attribute :>> performanceIndicators = "Referral turnaround time, incidents during grooming of referred dogs, vet satisfaction with communication.";
    }

    part vetReferralPathway : ReferralPathway {
        doc /* Vet referrals for grooming of dogs with health
             * conditions — inbound from vet to Paws. */
        attribute :>> pathwayName = "Vet referral for grooming";
        attribute :>> direction = ReferralDirection::inbound;
        attribute :>> referringEntity = "Local veterinary practices";
        attribute :>> referralCriteria = "Dog with health condition requiring specialist grooming awareness — skin conditions, post-surgical, mobility issues, anxiety.";
        attribute :>> referralProtocol = "Vet referral note with condition details and handling advice. Phone call for complex cases.";
        attribute :>> expectedResponseTime = "Acknowledgement within 2 working days. Appointment within 1 week.";
        attribute :>> feedbackMechanism = "Post-grooming note sent to vet for dogs with health conditions.";
        attribute :>> volumeTracking = "Referral volumes tracked monthly. Proportion of bookings from vet referrals.";
    }

    part groomingProductSupply : ExternalDependency {
        attribute :>> dependencyName = "Grooming product supply";
        attribute :>> provider = "Professional grooming product suppliers";
        attribute :>> dependencyDescription = "Supply of shampoos, conditioners, coat treatments, ear cleaners, and grooming tools.";
        attribute :>> criticality = DependencyCriticality::important;
        attribute :>> substitutability = "Multiple suppliers available for most products. Some breed-specific or sensitive-skin products have fewer suppliers. Brand switching straightforward for most products.";
        attribute :>> contingencyPlan = "Stock held for 4-6 weeks of standard products. Alternative supplier accounts maintained. Generic alternatives identified for specialist products.";
        attribute :>> contractualTerms = "Standard trade account. Monthly ordering with volume discount.";
        attribute :>> supplyRisk = "Low — diverse supplier market. Occasional discontinuation of specialist products.";
    }

    part localDogCommunity : CommunityRelationship {
        attribute :>> communityName = "Local dog owner community";
        attribute :>> communityDescription = "Dog owners in the local area — breed groups, social walking groups, social media communities.";
        attribute :>> relationshipToService = "Constitutive — the local dog-owning community is the customer base. Breed-specific knowledge flows both ways.";
        attribute :>> engagementMode = "Social media presence, breed group engagement, local dog events, grooming tips and advice sharing.";
        attribute :>> mutualBenefit = "Community gains expert grooming and breed-specific care advice. Paws gains breed knowledge, trust, and word-of-mouth referrals.";
        attribute :>> communityVoice = "Customer reviews, social media feedback, breed-specific grooming preference discussions, seasonal coat care advice requests.";
    }

    part pawsParticipation : ParticipationModel {
        doc /* Pet owner as informed participant — communicates breed
             * needs and health history, present during grooming. */
        attribute :>> participationName = "Owner consultation and handover";
        attribute :>> participantRole = "Informed participant — owner communicates needs and preferences, groomer delivers the service";
        attribute :>> participationDescription = "Owner communicates breed needs, health history, behavioural notes, and grooming preferences at check-in. Owner may be present or nearby during grooming. Post-grooming handover includes condition notes.";
        attribute :>> informationContribution = "Breed details, health conditions, behavioural notes (e.g. anxiety triggers), grooming style preferences, skin sensitivity, previous grooming history.";
        attribute :>> decisionInvolvement = "Consulted — owner expresses preferences, groomer advises on breed-appropriate options and makes professional decisions about safe handling.";
        attribute :>> selfServiceScope = "Online booking, viewing grooming notes, rebooking preferred services.";
        attribute :>> supportRequired = "Clear communication about grooming options, breed-specific care advice, transparent pricing for add-on services.";
    }
}

// =========================================================================
// PAWS DEMONSTRATOR — Resource and Financial Planning
// =========================================================================

package PawsResourceFinancial {
    private import ScalarValues::*;
    private import BusinessMetamodelGeneral::ResourcePlanning::*;
    private import BusinessMetamodelGeneral::FinancialPlanning::*;
    private import PawsBusinessModel::*;

    // -- Resource types ----------------------------------------

    part dogGroomer : ResourceType {
        doc /* Qualified dog groomer — the primary resource.
             * City & Guilds Level 3 in Dog Grooming or
             * equivalent. Breed-specific training preferred. */
        attribute :>> resourceTypeName = "Dog groomer";
        attribute :>> category = "personnel";
        attribute :>> acquisitionMethod = "employed";
        attribute :>> costProfile = "£16.50 per hour";
        attribute :>> capacityUnit = "FTE";
    }

    part groomingEquipment : ResourceType {
        doc /* Grooming tables, professional clippers, scissor
             * sets, blade sets, slicker brushes, combs. One
             * station per groomer. */
        attribute :>> resourceTypeName = "Grooming equipment";
        attribute :>> category = "equipment";
        attribute :>> acquisitionMethod = "purchased";
        attribute :>> costProfile = "£2,000 initial per station, £50/month maintenance and replacement";
        attribute :>> capacityUnit = "stations";
    }

    part bathAndDryingEquipment : ResourceType {
        doc /* Professional dog bath (height-adjustable), high-velocity
             * dryer, stand dryer. Shared across groomers. */
        attribute :>> resourceTypeName = "Bath and drying equipment";
        attribute :>> category = "equipment";
        attribute :>> acquisitionMethod = "purchased";
        attribute :>> costProfile = "£1,500 initial, £30/month maintenance";
        attribute :>> capacityUnit = "stations";
    }

    part salonPremises : ResourceType {
        attribute :>> resourceTypeName = "Salon premises";
        attribute :>> category = "estate";
        attribute :>> acquisitionMethod = "rented";
        attribute :>> costProfile = "£1,200 per month rent";
        attribute :>> capacityUnit = "premises";
    }

    part groomingConsumables : ResourceType {
        doc /* Shampoo, conditioner, finishing sprays, ear cleaner,
             * styptic powder, blade oil, bandanas/bows. Ongoing
             * variable cost scaling with appointment volume. */
        attribute :>> resourceTypeName = "Grooming consumables";
        attribute :>> category = "consumables";
        attribute :>> acquisitionMethod = "purchased";
        attribute :>> costProfile = "£2.50 per appointment average";
        attribute :>> capacityUnit = "units";
    }

    part bookingSystem : ResourceType {
        doc /* Online booking and appointment management software.
             * Handles scheduling, reminders, customer records,
             * and payment processing. */
        attribute :>> resourceTypeName = "Booking and management system";
        attribute :>> category = "technology";
        attribute :>> acquisitionMethod = "subscribed";
        attribute :>> costProfile = "£40 per month subscription";
        attribute :>> capacityUnit = "instances";
    }

    // -- Capability -------------------------------------------

    part deliverGroomingAppointment : Capability {
        attribute :>> capabilityName = "Deliver a grooming appointment";
        attribute :>> description = "Receive a dog, assess condition, perform grooming to breed standard or owner preference, and return the dog in good condition";
        attribute :>> requiredResources = "1 groomer + grooming station + bath/dryer + consumables + premises + booking system";
        attribute :>> enabledOfferingsDescription = "Full groom, Wash and tidy, Nail trim";
    }

    // -- Capacity model ---------------------------------------

    part standardDayCapacity : CapacityModel {
        doc /* Capacity model for a single groomer working a
             * standard day. Appointment duration varies by
             * service type and breed, so capacity is expressed
             * as a range. */
        attribute :>> resourceConfiguration = "1 groomer + 1 grooming station + shared bath/dryer";
        attribute :>> throughputPerPeriod = "5-7 appointments";
        attribute :>> periodUnit = "per day";
        attribute :>> assumptions = "8-hour working day, average 75 min per full groom including turnover, 45 min per wash-and-tidy, 15 min per nail trim. Mix of appointment types.";
        attribute :>> bottleneck = "Groomer time — one dog per groomer at a time";
    }

    // -- Resource constraint ----------------------------------

    part animalWelfareDuty : ResourceConstraint {
        doc /* General duty of care under the Animal Welfare Act
             * 2006. Not a specific regulatory framework like COSHH
             * — rather a general professional obligation to ensure
             * animals are not caused unnecessary suffering.
             *
             * This exercises ResourceConstraint with a general
             * professional governance posture, distinct from Suds'
             * specific regulatory constraint. */
        attribute :>> constraintName = "Animal welfare duty of care";
        attribute :>> constraintType = "regulatory";
        ref :>> affectedResource = dogGroomer;
        attribute :>> limit = "All grooming must be performed with due regard for animal welfare. Dogs showing signs of distress, pain, or health issues must have grooming paused or adapted. Owner to be notified of any concerns.";
        attribute :>> regulatorySourceDescription = "Animal Welfare Act 2006 — duty of care to animals under your control";
    }

    // -- Revenue stream ---------------------------------------

    part groomingRevenue : RevenueStream {
        attribute :>> streamName = "Grooming service revenue";
        attribute :>> sourceSegment = "Individual pet owners and regular customers";
        attribute :>> triggerEvent = "Grooming appointment completed";
        ref :>> pricingModel = perAppointmentPricing;
        attribute :>> projectedVolume = "6 appointments per day average (1 groomer)";
    }

    // -- Cost drivers -----------------------------------------

    part groomerLabourCosts : CostDriver {
        attribute :>> driverName = "Groomer labour";
        ref :>> linkedResource = dogGroomer;
        attribute :>> costBehaviour = "semi-variable — fixed shifts, overtime for busy periods";
        attribute :>> estimatedUnitCost = 16.50;
        attribute :>> scalingFactor = "per hour";
    }

    part consumableCosts : CostDriver {
        attribute :>> driverName = "Grooming consumables";
        ref :>> linkedResource = groomingConsumables;
        attribute :>> costBehaviour = "variable";
        attribute :>> estimatedUnitCost = 2.50;
        attribute :>> scalingFactor = "per appointment";
    }

    part salonRentCosts : CostDriver {
        attribute :>> driverName = "Salon rent";
        ref :>> linkedResource = salonPremises;
        attribute :>> costBehaviour = "fixed";
        attribute :>> estimatedUnitCost = 1200.0;
        attribute :>> scalingFactor = "per month";
    }

    part equipmentMaintenanceCosts : CostDriver {
        attribute :>> driverName = "Equipment maintenance and replacement";
        ref :>> linkedResource = groomingEquipment;
        attribute :>> costBehaviour = "fixed";
        attribute :>> estimatedUnitCost = 80.0;
        attribute :>> scalingFactor = "per month";
    }

    // -- Unit economics ---------------------------------------

    part fullGroomEconomics : UnitEconomics {
        doc /* Per-appointment economics for a full groom.
             * Average across breed sizes. Revenue varies by
             * size band; costs are relatively stable. */
        ref :>> offering = fullGroom;
        attribute :>> revenuePerUnit = 48.0;
        attribute :>> costPerUnit = 22.0;
        attribute :>> marginPerUnit = 26.0;
        attribute :>> breakdownNotes = "Labour £16.50 (avg 60 min), consumables £2.50, equipment wear £1.50, booking system £1.50. Rent excluded (fixed cost). Revenue is weighted average across size bands.";
    }

    part washAndTidyEconomics : UnitEconomics {
        doc /* Per-appointment economics for wash and tidy.
             * Shorter appointment, lower price, but good margin
             * due to reduced labour time. */
        ref :>> offering = washAndTidy;
        attribute :>> revenuePerUnit = 28.0;
        attribute :>> costPerUnit = 13.0;
        attribute :>> marginPerUnit = 15.0;
        attribute :>> breakdownNotes = "Labour £8.25 (avg 30 min), consumables £2.00, equipment wear £1.25, booking system £1.50. Rent excluded.";
    }

    part nailTrimEconomics : UnitEconomics {
        doc /* Per-appointment economics for nail trim.
             * Quick, low-cost service. Good margin as a
             * standalone; excellent as an add-on since the
             * dog is already on the table. */
        ref :>> offering = nailTrimAddOn;
        attribute :>> revenuePerUnit = 10.0;
        attribute :>> costPerUnit = 3.50;
        attribute :>> marginPerUnit = 6.50;
        attribute :>> breakdownNotes = "Labour £4.13 (15 min) as standalone. As add-on: marginal cost near zero (dog already present). Consumables negligible.";
    }

    // -- Pricing model ----------------------------------------

    part perAppointmentPricing : PricingModel {
        doc /* Per-appointment pricing with breed/size bands.
             * Three size categories: small (up to 10kg),
             * medium (10-25kg), large (25kg+). Double-coated
             * breeds attract a surcharge. */
        attribute :>> pricingModelName = "Per-appointment with breed/size bands";
        attribute :>> pricingType = PricingType::perEpisode;
        attribute :>> basePrice = 35.0;
        attribute :>> adjustmentLogic = "Full groom: small £35, medium £48, large £65. Wash and tidy: small £20, medium £28, large £40. Nail trim: £10 standalone, £5 add-on. Double-coated breed surcharge +£10.";
        attribute :>> applicableOfferings = "Full groom, Wash and tidy, Nail trim";
    }
}

// =========================================================================
// PAWS DEMONSTRATOR — Governance: Animal Welfare Duty of Care
// =========================================================================
//
// Exercises the governance vocabulary (A8, J8) with a general
// professional governance posture — distinct from Suds' specific
// COSHH regulatory framework.
//
// No constraint def / satisfy chain here. The Animal Welfare Act
// 2006 imposes a general duty of care, not specific testable
// conditions expressible as Boolean predicates. The governance
// traceability is: requirement → audit evidence (without the
// intermediate constraint formalisation).
//
// This is a valid cross-domain test: not all governance is
// specific-regulation governance. The vocabulary should handle
// both postures.
//
// Session 44 (19 March 2026): initial governance model.
// =========================================================================

package PawsGovernance {
    private import ScalarValues::*;
    private import BusinessMetamodelGeneral::ServiceConcept::ExternalReference;
    private import BusinessMetamodelGeneral::GovernanceMapping::*;

    doc /* Animal welfare governance for the Paws grooming service.
         * Demonstrates the governance vocabulary under a general
         * professional duty of care — no specific regulation like
         * COSHH, but still requiring auditable evidence of
         * responsible practice.
         *
         * The GovernanceRequirement and AuditEvidenceRecord part
         * defs are General BMM vocabulary from
         * BusinessMetamodelGeneral::GovernanceMapping. No domain-specific
         * constraint defs needed — the obligations are general,
         * not formally testable as Boolean predicates. */

    // -- Governance Requirement --------------------------------

    requirement animalWelfareDutyOfCare : GovernanceRequirement {
        doc /* Animal Welfare Act 2006 — duty of care to animals
             * under your control. Applies to any person responsible
             * for an animal, including during grooming. Five welfare
             * needs: suitable environment, suitable diet, ability to
             * exhibit normal behaviour, housing with or apart from
             * other animals, protection from pain, suffering, injury
             * and disease.
             *
             * This is a general duty, not a prescriptive set of
             * testable conditions. Compliance is demonstrated through
             * professional practice, training, and incident-free
             * operation — hence audit evidence records rather than
             * formal constraint satisfaction. */

        attribute :>> requirementId = "PAWS-GOV-001";
        attribute :>> title = "Animal welfare duty of care during grooming";
        attribute :>> regulatorySource = "Animal Welfare Act 2006 — Section 9 (duty of person responsible for animal to ensure welfare)";
        attribute :>> complianceDescription = "All grooming must be performed with due regard for the animal's welfare. Dogs must not be caused unnecessary suffering. Signs of distress must be recognised and acted upon. Health concerns observed during grooming must be communicated to the owner. Equipment must be maintained in safe working order. The grooming environment must be suitable for dogs.";
        attribute :>> evidenceRequired = "Public liability insurance, incident and observation log, first aid kit inspection records, groomer training and CPD records";
    }

    // -- Audit Evidence Records -------------------------------

    part publicLiabilityInsurance : AuditEvidenceRecord {
        doc /* Current public liability insurance certificate.
             * Required for any business handling animals on
             * premises. Covers injury to animals and third parties. */
        attribute :>> evidenceType = "insurance certificate";
        attribute :>> evidenceDescription = "Current public liability insurance policy covering dog grooming services. Must cover injury to animals in care and injury to third parties on premises.";
        attribute :>> retentionPeriod = "Duration of policy plus 6 years";
        attribute :>> responsibleRole = "Business owner";
        attribute :>> frequency = "Annual renewal — certificate held on file";
    }

    part incidentAndObservationLog : AuditEvidenceRecord {
        doc /* Log of any incidents during grooming (nicks, stress
             * reactions, health concerns observed) and actions
             * taken. Demonstrates duty of care through transparent
             * recording and appropriate response. */
        attribute :>> evidenceType = "incident log";
        attribute :>> evidenceDescription = "Dated record of any grooming incidents (cuts, abrasions, stress responses), health observations (lumps, skin conditions, parasites), and actions taken (grooming paused, owner notified, vet referral suggested). Includes near-misses.";
        attribute :>> retentionPeriod = "5 years";
        attribute :>> responsibleRole = "Groomer on duty";
        attribute :>> frequency = "Per incident — reviewed weekly by business owner";
    }

    part firstAidKitInspection : AuditEvidenceRecord {
        doc /* Periodic inspection of the animal first aid kit.
             * Styptic powder, bandages, antiseptic, eye wash,
             * emergency vet contact details. */
        attribute :>> evidenceType = "inspection record";
        attribute :>> evidenceDescription = "Dated record of animal first aid kit inspection: styptic powder stock, bandage supply, antiseptic availability, eye wash expiry check, emergency vet contact details current.";
        attribute :>> retentionPeriod = "3 years";
        attribute :>> responsibleRole = "Business owner or senior groomer";
        attribute :>> frequency = "Monthly";
    }

    // -- External References ----------------------------------

    part animalWelfareActReference : ExternalReference {
        doc /* The Animal Welfare Act 2006 — the primary legislative
             * reference for duty of care obligations. */
        attribute :>> referenceType = "primary legislation";
        attribute :>> referenceId = "AWA-2006";
        attribute :>> referenceSource = "UK Parliament — Animal Welfare Act 2006, Section 9";
        attribute :>> referenceNotes = "Duty of person responsible for animal to ensure welfare. Five welfare needs. Applies to any person responsible for an animal, including during commercial grooming services.";
    }
}

// =========================================================================
// PAWS DEMONSTRATOR — Canonical Runtime Types (Multi-Axis Status)
// =========================================================================
//
// Session 255 — First tenant declaration of W-094 (multi-axis status
// primitive). Source specification: ontara-model-multi-axis-status-
// primitive-2026-04-22 (S253). Canonical worked example — Paws Booking
// with four tenant-declared axes. (Until S514 it was described as five,
// with a platform-inherited epistemic axis; that axis was retired by
// ADR-011. Mode and method now sit on the platform's record of each write.)
//
// Stratum-and-side locus: Configured-Model stratum, business side
// (tenant's DBM — Domain Business Model for Paws). Per the strengthened
// A4 (tenant configured-model content).
//
// Scope of this package:
//   - Booking: first canonical runtime type for Paws, specialising
//     BusinessMetamodelGeneral::CanonicalRuntime::CanonicalRuntimeType. Declares four tenant axes
//     (lifecycle, confirmation, payment, cancellation). No axis is
//     inherited from the platform (S514, ADR-011).
//
// Out of scope for this session:
//   - Pet canonical type (S253 §8.2 — no tenant axes at v1).
//   - Cross-axis consequence rules (S253 §6) — cancellation-policy
//     evaluator architecture resolved, implementation deferred.
//   - Further Paws canonical types (Appointment, PaymentRecord, etc.).
//   - Tenant BMM-concern-structured content beyond axis declarations.
//
// Per S253 §8.1 — the (now four-axis) Booking is the driving worked example
// for W-094 first implementation.
//
// =========================================================================

package PawsCanonicalRuntime {
    private import ScalarValues::*;
    private import BusinessMetamodelGeneral::CanonicalRuntime::*;

    doc /* Canonical runtime types for the Paws tenant. At v1, the
         * Booking type is the worked example for multi-axis status.
         *
         * Stratum-and-side locus: Configured-Model stratum, business
         * side. Tenant configured-model content — not metamodel
         * vocabulary. The StatusAxis part def and its supporting types
         * live in CanonicalRuntime (BMM General, Metamodel stratum).
         *
         * Four-axis Booking (S253 §8.1 as amended by ADR-011, S514):
         * lifecycle, confirmation, payment, cancellation. The record
         * of each write carries mode and method beside the tuple.
         *
         * Cross-axis rules (cancellation → payment refund, lifecycle →
         * payment on-check-in hold, confirmation preconditions on
         * lifecycle) are specified in S253 §6 but not yet implemented
         * in this first implementation pass. */

    // =====================================================================
    // BOOKING — Four-axis canonical runtime type (S253 §8.1; ADR-011)
    // =====================================================================

    part def Booking :> CanonicalRuntimeType {
        doc /* Paws Booking canonical runtime type.
             *
             * A Booking represents a scheduled grooming appointment —
             * its existence begins when the owner books (online or
             * walk-in) and ends when the engagement closes post-
             * grooming. The runtime instance carries a four-axis
             * status tuple at all times:
             *
             * - lifecycle (ordered): scheduled → checked-in →
             *     in-progress → ready → collected → closed
             * - confirmation (unordered): the confirmation dialogue
             *     between customer and tenant
             * - payment (unordered): deposit, final payment, and
             *     refund states
             * - cancellation (unordered): active / cancelled-by-owner
             *     / cancelled-by-tenant / no-show
             *
             * No epistemic axis (retired S514, ADR-011). Whether a
             * record of the booking is real or simulated, and whether
             * it was direct, inferred or predicted, is carried by the
             * platform's record of the write, not by the booking.
             *
             * Source: S253 §8.1. Configured-model content (tenant's
             * DBM). */

        // -- lifecycle axis (ordered enumeration) -------------------

        part lifecycleAxis : StatusAxis {
            :>> axisName = "lifecycle";
            :>> axisDescription = "The lifecycle stage of the booking from scheduling through to closure of the engagement.";
            :>> axisScope = AxisScope::tenantDeclared;
            :>> axisAuthority = (AxisAuthority::operatorSide, AxisAuthority::systemSide);
            :>> defaultValue = "scheduled";

            part :>> valueSpace : ValueSpace {
                :>> valueShape = ValueSpaceShape::orderedEnum;
                :>> enumValues = ("scheduled", "checkedIn", "inProgress",
                                  "ready", "collected", "closed");
            }

            part scheduledToCheckedIn : AxisTransition {
                :>> fromValue = "scheduled";
                :>> toValue = "checkedIn";
                :>> transitionLabel = "owner arrives and drops off dog";
                :>> requiredAuthority = (AxisAuthority::operatorSide);
            }

            part checkedInToInProgress : AxisTransition {
                :>> fromValue = "checkedIn";
                :>> toValue = "inProgress";
                :>> transitionLabel = "grooming begins";
                :>> requiredAuthority = (AxisAuthority::operatorSide);
            }

            part inProgressToReady : AxisTransition {
                :>> fromValue = "inProgress";
                :>> toValue = "ready";
                :>> transitionLabel = "grooming complete, awaiting collection";
                :>> requiredAuthority = (AxisAuthority::operatorSide);
            }

            part readyToCollected : AxisTransition {
                :>> fromValue = "ready";
                :>> toValue = "collected";
                :>> transitionLabel = "owner collects dog";
                :>> requiredAuthority = (AxisAuthority::operatorSide);
            }

            part collectedToClosed : AxisTransition {
                :>> fromValue = "collected";
                :>> toValue = "closed";
                :>> transitionLabel = "engagement closed, final payment settled";
                :>> requiredAuthority = (AxisAuthority::systemSide);
            }
        }

        // -- confirmation axis (unordered enumeration) --------------

        part confirmationAxis : StatusAxis {
            :>> axisName = "confirmation";
            :>> axisDescription = "The state of the confirmation dialogue with the customer — whether the booking has been reconfirmed ahead of the appointment.";
            :>> axisScope = AxisScope::tenantDeclared;
            :>> axisAuthority = (AxisAuthority::customerSide, AxisAuthority::systemSide);
            :>> defaultValue = "unconfirmed";

            part :>> valueSpace : ValueSpace {
                :>> valueShape = ValueSpaceShape::unorderedEnum;
                :>> enumValues = ("unconfirmed", "awaitingReply",
                                  "confirmed", "confirmationLapsed");
            }

            part unconfirmedToAwaitingReply : AxisTransition {
                :>> fromValue = "unconfirmed";
                :>> toValue = "awaitingReply";
                :>> transitionLabel = "confirmation request sent to customer";
                :>> requiredAuthority = (AxisAuthority::systemSide);
            }

            part awaitingReplyToConfirmed : AxisTransition {
                :>> fromValue = "awaitingReply";
                :>> toValue = "confirmed";
                :>> transitionLabel = "customer confirms booking";
                :>> requiredAuthority = (AxisAuthority::customerSide);
            }

            part awaitingReplyToLapsed : AxisTransition {
                :>> fromValue = "awaitingReply";
                :>> toValue = "confirmationLapsed";
                :>> transitionLabel = "confirmation window passed without reply";
                :>> requiredAuthority = (AxisAuthority::systemSide);
            }
        }

        // -- payment axis (unordered enumeration) -------------------

        part paymentAxis : StatusAxis {
            :>> axisName = "payment";
            :>> axisDescription = "The state of payment for this booking — deposit, final settlement, and refund conditions.";
            :>> axisScope = AxisScope::tenantDeclared;
            :>> axisAuthority = (AxisAuthority::systemSide);
            :>> defaultValue = "unpaid";

            part :>> valueSpace : ValueSpace {
                :>> valueShape = ValueSpaceShape::unorderedEnum;
                :>> enumValues = ("unpaid", "preAuthHeld", "depositHeld",
                                  "fullyPrepaid", "paidInFull",
                                  "partiallyRefunded", "fullyRefunded");
            }

            part unpaidToDepositHeld : AxisTransition {
                :>> fromValue = "unpaid";
                :>> toValue = "depositHeld";
                :>> transitionLabel = "deposit charged at booking";
                :>> requiredAuthority = (AxisAuthority::systemSide);
            }

            part depositHeldToPaidInFull : AxisTransition {
                :>> fromValue = "depositHeld";
                :>> toValue = "paidInFull";
                :>> transitionLabel = "final payment taken at collection";
                :>> requiredAuthority = (AxisAuthority::systemSide);
            }

            part depositHeldToPartiallyRefunded : AxisTransition {
                :>> fromValue = "depositHeld";
                :>> toValue = "partiallyRefunded";
                :>> transitionLabel = "partial refund issued (late cancellation)";
                :>> requiredAuthority = (AxisAuthority::systemSide);
            }

            part depositHeldToFullyRefunded : AxisTransition {
                :>> fromValue = "depositHeld";
                :>> toValue = "fullyRefunded";
                :>> transitionLabel = "full refund issued (early cancellation)";
                :>> requiredAuthority = (AxisAuthority::systemSide);
            }
        }

        // -- cancellation axis (unordered enumeration) --------------

        part cancellationAxis : StatusAxis {
            :>> axisName = "cancellation";
            :>> axisDescription = "Whether this booking has been cancelled, and if so by which party; or no-show recorded.";
            :>> axisScope = AxisScope::tenantDeclared;
            :>> axisAuthority = (AxisAuthority::customerSide, AxisAuthority::operatorSide);
            :>> defaultValue = "active";

            part :>> valueSpace : ValueSpace {
                :>> valueShape = ValueSpaceShape::unorderedEnum;
                :>> enumValues = ("active", "cancelledByOwner",
                                  "cancelledByTenant", "noShow");
            }

            part activeToCancelledByOwner : AxisTransition {
                :>> fromValue = "active";
                :>> toValue = "cancelledByOwner";
                :>> transitionLabel = "owner cancels the booking";
                :>> requiredAuthority = (AxisAuthority::customerSide);
            }

            part activeToCancelledByTenant : AxisTransition {
                :>> fromValue = "active";
                :>> toValue = "cancelledByTenant";
                :>> transitionLabel = "tenant cancels the booking";
                :>> requiredAuthority = (AxisAuthority::operatorSide);
            }

            part activeToNoShow : AxisTransition {
                :>> fromValue = "active";
                :>> toValue = "noShow";
                :>> transitionLabel = "appointment time passed without customer arrival";
                :>> requiredAuthority = (AxisAuthority::operatorSide);
            }
        }
    }
}

// =========================================================================
// PAWS DOMAIN REGISTRATION — tenant domain registration
// =========================================================================
//
// OP-132 step 10 (S515, ADR-012 group H). The DomainIdentity (BMG) and
// DomainConfiguration (SMG) instances for this tenant, formerly in
// Foundation's DomainRegistry. The pair is linked one way, from the
// configuration to the identity (Action 2).
// =========================================================================

package PawsDomainRegistration {
    private import BusinessMetamodelGeneral::DomainIdentityTypes::*;
    private import SystemMetamodelGeneral::DomainConfigurationTypes::*;

    // --- Paws (Dog Grooming) ------------------------------------

    part pawsIdentity : DomainIdentity {
        doc /* Pedagogical anchoring and cross-domain validation
             * domain — appointment-based dog grooming service.
             * Dual purpose (S142-D6): simple enough to introduce
             * concepts, different enough to validate generalisation.
             * Breed/size surcharges. Locally licensed (Animal
             * Welfare Act duties; some local authorities require
             * grooming-specific licences). */

        attribute :>> regulatoryShape = RegulatoryShape::locallyLicensed;
        attribute :>> bmmVocabularyScope = BmmVocabularyScope::generalOnly;
        attribute :>> domainPurpose = (DomainPurpose::pedagogicalAnchoring, DomainPurpose::crossDomainValidation);
        attribute :>> jurisdiction = Jurisdiction::england;
        attribute :>> organisationalForm = OrganisationalForm::registeredIndividual;
        attribute :>> authorisationRequiredToTrade = false;
        attribute :>> description = "Pedagogical anchoring and cross-domain validation domain — appointment-based dog grooming. Breed/size surcharges.";
        attribute :>> introducedSession = 43;
    }

    part pawsConfiguration : DomainConfiguration {
        attribute :>> canonicalKey = "paws";
        attribute :>> displayLabel = "Paws";
        attribute :>> fullName = "Paws (Dog Grooming)";
        attribute :>> packageName = "PawsBusinessModel";
        attribute :>> modelPath = "exercises/paws-demonstrator/model";
        attribute :>> isActive = true;
        ref :>> domainIdentity = pawsIdentity;
    }
}
