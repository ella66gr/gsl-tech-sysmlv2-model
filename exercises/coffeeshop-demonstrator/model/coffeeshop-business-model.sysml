// =========================================================================
// Coffee Shop Business Model Extension
// =========================================================================
// Validates that the BusinessMetamodelGeneral::ServiceConcept and
// BusinessMetamodelGeneral::ActivityModel part defs accommodate a simple service
// business. Tests cross-project import from the main model.
//
// Phase 1 demonstrator (Session 14, 10 March 2026):
//   ServiceConcept, ActivityModel, ActivityGranularity usages.
// CSW Extension Phase 1 (Session 20, 12 March 2026):
//   CatalogueEntry usages for all 11 menu items.
//   catalogueMaintenance activity type.
//
// Companion: gsl-plan-workstream-csw-extension-2026-03-12.md
// =========================================================================

package CoffeeShopBusinessModel {
    private import ScalarValues::*;
    private import BusinessMetamodelGeneral::ServiceConcept::CustomerSegment;
    private import BusinessMetamodelGeneral::ServiceConcept::ServiceOffering;
    private import BusinessMetamodelGeneral::ServiceConcept::Channel;
    private import BusinessMetamodelGeneral::ActivityModel::*;
    private import SystemMetamodelGeneral::Persistence::*;        // PersistenceLayer, PersistencePolicy
    private import CoffeeShop::*;
    private import BusinessMetamodelGeneral::StakeholderModel::*;

    // Import note: ServiceConcept is imported by name, not by wildcard
    // (S518, S0.3). CoffeeShop::CatalogueEntry specialises the General
    // CatalogueEntry and keeps its name, so a wildcard import of
    // ServiceConcept would bring a second CatalogueEntry into this
    // namespace (the name collision first introduced at Session 29).
    // Catalogue entry usages below still write CoffeeShop::CatalogueEntry.

    doc /* Coffee shop business model extension. Instantiates the
         * ServiceConcept and ActivityModel part defs from the main
         * BusinessModel package to validate that the abstractions
         * work for a simple service business.
         *
         * If these feel over-engineered for a coffee shop, the
         * abstractions may need simplifying. If they feel natural,
         * the design is sound. */

    // -- Service Concept --------------------------------------

    part walkInCustomers : CustomerSegment {
        attribute :>> segmentName = "Walk-in customers";
        attribute :>> description = "Passers-by and regulars who visit the counter";
        attribute :>> needs = "Quick, good coffee at a fair price";
        attribute :>> acquisitionChannel = "Foot traffic, signage, word of mouth";
        attribute :>> willingnessToPayIndicator = "medium";
    }

    part drinkOrder : ServiceOffering {
        doc /* The core (and only) service offering for the coffee
             * shop. Maps to the existing fulfil-drink pathway. */
        attribute :>> offeringName = "Drink order";
        attribute :>> description = "Customer orders and receives a prepared drink";
        attribute :>> scope = "Order taking, drink preparation, serving";
        attribute :>> pricingBasis = "per-item";
        attribute :>> estimatedDurationWeeks = 0;  // immediate service
        attribute :>> clinicalPathwayRef = "fulfil-drink-orchestration";
    }

    part counterService : Channel {
        attribute :>> channelName = "Counter service";
        attribute :>> description = "In-person ordering at the shop counter";
        attribute :>> channelType = "acquisition and delivery";
        attribute :>> estimatedReach = "local — foot traffic radius";
        attribute :>> estimatedCostLevel = "low";
        attribute :>> conversionNotes = "Very high — customers at the counter are ready to buy";
    }

    // -- Activity Model ---------------------------------------
    //
    // Five activity types, one per category, demonstrating
    // the taxonomy for a simple service business.

    part makeDrink : ActivityType {
        doc /* Service delivery: the core value-producing activity.
             * Already modelled as pathway steps in the fulfil-drink
             * action flow. */
        attribute :>> activityTypeName = "Make drink";
        attribute :>> activityCategory = ActivityCategory::serviceDelivery;
        attribute :>> description = "Prepare and serve a customer drink order";
        attribute :>> expectedDurationMinutes = 4;
        attribute :>> frequencyNotes = "Per customer order";
    }

    part prepAndClean : ActivityType {
        doc /* Service enabling: necessary to support delivery but
             * not directly visible to the customer. */
        attribute :>> activityTypeName = "Prep ingredients and clean equipment";
        attribute :>> activityCategory = ActivityCategory::serviceEnabling;
        attribute :>> description = "Grind beans, prepare milk, clean portafilter and steam wand";
        attribute :>> expectedDurationMinutes = 30;
        attribute :>> frequencyNotes = "Twice daily — opening and mid-shift";
    }

    part healthSafetyChecks : ActivityType {
        attribute :>> activityTypeName = "Health and safety checks";
        attribute :>> activityCategory = ActivityCategory::governance;
        attribute :>> description = "Temperature logs, hygiene checks, stock rotation, equipment inspection";
        attribute :>> expectedDurationMinutes = 15;
        attribute :>> frequencyNotes = "Daily — opening";
    }

    part baristaTraining : ActivityType {
        attribute :>> activityTypeName = "Barista training";
        attribute :>> activityCategory = ActivityCategory::development;
        attribute :>> description = "Skills development, new menu items, latte art practice";
        attribute :>> expectedDurationMinutes = 60;
        attribute :>> frequencyNotes = "Weekly";
    }

    part tillReconciliation : ActivityType {
        attribute :>> activityTypeName = "Till reconciliation";
        attribute :>> activityCategory = ActivityCategory::overhead;
        attribute :>> description = "Cash count, card terminal reconciliation, daily banking";
        attribute :>> expectedDurationMinutes = 15;
        attribute :>> frequencyNotes = "Daily — closing";
    }

    part catalogueMaintenance : ActivityType {
        doc /* Administrative data management: maintaining the
             * product catalogue, updating prices, managing
             * availability status and inventory records. */
        attribute :>> activityTypeName = "Catalogue maintenance";
        attribute :>> activityCategory = ActivityCategory::overhead;
        attribute :>> description = "Add, edit, and manage menu items, pricing, and stock levels";
        attribute :>> expectedDurationMinutes = 15;
        attribute :>> frequencyNotes = "As needed — typically weekly or when menu changes";
    }

    // -- Granularity policy ------------------------------------

    part serviceDeliveryGranularity : ActivityGranularity {
        doc /* Service delivery is at tracked level from day one —
             * the pathway model already produces observable events
             * for every drink order. */
        attribute :>> businessArea = "Service delivery";
        attribute :>> currentLevel = GranularityLevel::tracked;
        attribute :>> targetLevel = GranularityLevel::tracked;
        attribute :>> migrationNotes = "Already tracked via pathway workflow events";
    }

    part enablingGranularity : ActivityGranularity {
        attribute :>> businessArea = "Service enabling";
        attribute :>> currentLevel = GranularityLevel::envelope;
        attribute :>> targetLevel = GranularityLevel::category;
        attribute :>> migrationNotes = "Could track prep sessions as discrete events if costing precision needed";
    }

    part governanceGranularity : ActivityGranularity {
        attribute :>> businessArea = "Governance";
        attribute :>> currentLevel = GranularityLevel::envelope;
        attribute :>> targetLevel = GranularityLevel::envelope;
        attribute :>> migrationNotes = "Low volume — envelope estimate sufficient";
    }

    part developmentGranularity : ActivityGranularity {
        attribute :>> businessArea = "Development";
        attribute :>> currentLevel = GranularityLevel::envelope;
        attribute :>> targetLevel = GranularityLevel::envelope;
        attribute :>> migrationNotes = "Weekly training session — envelope adequate";
    }

    part overheadGranularity : ActivityGranularity {
        attribute :>> businessArea = "Overhead";
        attribute :>> currentLevel = GranularityLevel::envelope;
        attribute :>> targetLevel = GranularityLevel::envelope;
        attribute :>> migrationNotes = "Low volume routine admin — envelope adequate";
    }

    // -- Catalogue Entries ------------------------------------
    //
    // Business decisions about what to offer and at what price.
    // Each entry references a menu item and adds business context.
    // Provision type classification determines inventory semantics.
    // The item ref is structural — specific MenuItem binding is a
    // runtime/database concern, not modelled here.

    // -- Hot drinks --

    part flatWhiteCatalogue : CoffeeShop::CatalogueEntry {
        doc /* Flat White — flagship espresso drink. */
        attribute :>> pricePence = 280;
        attribute :>> priceDisplay = "£2.80";
        attribute :>> availability = AvailabilityStatus::active;
        attribute :>> provisionKind = ProvisionType::prepared;
        attribute :>> effectiveDate = "2026-03-12";
        attribute :>> statusNotes = "Core menu item";
    }

    part latteCatalogue : CoffeeShop::CatalogueEntry {
        attribute :>> pricePence = 280;
        attribute :>> priceDisplay = "£2.80";
        attribute :>> availability = AvailabilityStatus::active;
        attribute :>> provisionKind = ProvisionType::prepared;
        attribute :>> effectiveDate = "2026-03-12";
        attribute :>> statusNotes = "Core menu item";
    }

    part americanoCatalogue : CoffeeShop::CatalogueEntry {
        attribute :>> pricePence = 250;
        attribute :>> priceDisplay = "£2.50";
        attribute :>> availability = AvailabilityStatus::active;
        attribute :>> provisionKind = ProvisionType::prepared;
        attribute :>> effectiveDate = "2026-03-12";
        attribute :>> statusNotes = "Core menu item";
    }

    part cappuccinoCatalogue : CoffeeShop::CatalogueEntry {
        attribute :>> pricePence = 280;
        attribute :>> priceDisplay = "£2.80";
        attribute :>> availability = AvailabilityStatus::active;
        attribute :>> provisionKind = ProvisionType::prepared;
        attribute :>> effectiveDate = "2026-03-12";
        attribute :>> statusNotes = "Core menu item";
    }

    part espressoCatalogue : CoffeeShop::CatalogueEntry {
        attribute :>> pricePence = 200;
        attribute :>> priceDisplay = "£2.00";
        attribute :>> availability = AvailabilityStatus::active;
        attribute :>> provisionKind = ProvisionType::prepared;
        attribute :>> effectiveDate = "2026-03-12";
        attribute :>> statusNotes = "Core menu item — single size only";
    }

    // -- Cold drinks --

    part icedLatteCatalogue : CoffeeShop::CatalogueEntry {
        attribute :>> pricePence = 320;
        attribute :>> priceDisplay = "£3.20";
        attribute :>> availability = AvailabilityStatus::active;
        attribute :>> provisionKind = ProvisionType::prepared;
        attribute :>> effectiveDate = "2026-03-12";
        attribute :>> statusNotes = "Seasonal favourite";
    }

    part coldBrewCatalogue : CoffeeShop::CatalogueEntry {
        attribute :>> pricePence = 300;
        attribute :>> priceDisplay = "£3.00";
        attribute :>> availability = AvailabilityStatus::active;
        attribute :>> provisionKind = ProvisionType::prepared;
        attribute :>> effectiveDate = "2026-03-12";
        attribute :>> statusNotes = "Slow-steeped — 12hr preparation";
    }

    // -- New drinks --

    part mochaLatteCatalogue : CoffeeShop::CatalogueEntry {
        doc /* Mocha Latte — new addition, March 2026. */
        attribute :>> pricePence = 380;
        attribute :>> priceDisplay = "£3.80";
        attribute :>> availability = AvailabilityStatus::active;
        attribute :>> provisionKind = ProvisionType::prepared;
        attribute :>> effectiveDate = "2026-03-12";
        attribute :>> statusNotes = "New menu item — espresso with chocolate and steamed milk";
    }

    part frappeCatalogue : CoffeeShop::CatalogueEntry {
        doc /* Frappe — new addition, March 2026. */
        attribute :>> pricePence = 420;
        attribute :>> priceDisplay = "£4.20";
        attribute :>> availability = AvailabilityStatus::active;
        attribute :>> provisionKind = ProvisionType::prepared;
        attribute :>> effectiveDate = "2026-03-12";
        attribute :>> statusNotes = "New menu item — blended iced coffee";
    }

    // -- Food items (bought-in) --

    part gingerBiscuitCatalogue : CoffeeShop::CatalogueEntry {
        doc /* Ginger Biscuit — new addition, March 2026.
             * First bought-in item. Inventory tracking applies. */
        attribute :>> pricePence = 180;
        attribute :>> priceDisplay = "£1.80";
        attribute :>> availability = AvailabilityStatus::active;
        attribute :>> provisionKind = ProvisionType::boughtIn;
        attribute :>> effectiveDate = "2026-03-12";
        attribute :>> statusNotes = "New menu item — bought-in, stock tracked";
    }

    part oatBarCatalogue : CoffeeShop::CatalogueEntry {
        doc /* Oat Bar — new addition, March 2026.
             * Bought-in, vegan, gluten-free. */
        attribute :>> pricePence = 220;
        attribute :>> priceDisplay = "£2.20";
        attribute :>> availability = AvailabilityStatus::active;
        attribute :>> provisionKind = ProvisionType::boughtIn;
        attribute :>> effectiveDate = "2026-03-12";
        attribute :>> statusNotes = "New menu item — bought-in, vegan, GF, stock tracked";
    }

    // -- Persistence Policies ---------------------------------
    //
    // System meta model instantiation: explicit
    // architectural reasoning for where each CSW domain concept
    // is persisted and why. Rewritten at S518 (S0.3) for S515 D1:
    // runtime content is held in the knowledge graph; the process
    // engine holds only private workflow state. No Cafe policy
    // targets businessDatabase or clinicalDataRepository.
    //
    // S525 (S0.5 Pass B7, H-0646): each policy names its concept by
    // typed reference (ref :>> domainConcept : <type>), and sets at
    // least one characteristic. orderRecordPolicy now references
    // Order; orderLinePolicy added. feedbackRecordPolicy, which named
    // "FeedbackRecord", is removed: the Cafe has no feedback type, and
    // Ella chose removal over adding one (S525). Feedback's placement
    // (DSR content, in the knowledge graph; S515 D1) returns with a
    // feedback type when a stage needs one.
    //
    // Added Session 29: CSW Extension Phase 10 (item 8.3).
    // Source: gsl-spec-catalogue-inventory-v2.1.md §8.3

    part catalogueEntryPolicy : PersistencePolicy {
        doc /* Runtime content: the catalogue, prices and availability
             * are held as triples in the knowledge graph (H-0264;
             * S515 D1). */
        ref :>> domainConcept : CoffeeShop::CatalogueEntry;
        attribute :>> targetLayer = PersistenceLayer::knowledgeGraph;
        attribute :>> rationale = "The catalogue, prices and availability are runtime content, held in the knowledge graph (H-0264).";
        attribute :>> characteristics = DataCharacteristic::referenceData;
    }

    part inventoryRecordPolicy : PersistencePolicy {
        doc /* Runtime operational state, held as triples in the knowledge
             * graph with the catalogue entry it counts (S515 D1). */
        ref :>> domainConcept : InventoryRecord;
        attribute :>> targetLayer = PersistenceLayer::knowledgeGraph;
        attribute :>> rationale = "Stock levels are runtime operational state, held in the knowledge graph beside the catalogue (S515 D1).";
        attribute :>> characteristics = (DataCharacteristic::highFrequencyUpdate, DataCharacteristic::relationalJoins);
    }

    part orderRecordPolicy : PersistencePolicy {
        doc /* Orders are DBR content: the record of the business's own
             * transactions, held in the knowledge graph (S515 D1). */
        ref :>> domainConcept : Order;
        attribute :>> targetLayer = PersistenceLayer::knowledgeGraph;
        attribute :>> rationale = "Orders are DBR content, held in the knowledge graph (S515 D1).";
        attribute :>> characteristics = DataCharacteristic::transactionalIntegrity;
    }

    part orderLinePolicy : PersistencePolicy {
        doc /* Order lines are part of the order's DBR content, written
             * with their order and held in the knowledge graph (S515 D1).
             * Each line carries its own preparation axis, moved as the
             * line is made (S0.4). Added S525 (S0.5 Pass B7). */
        ref :>> domainConcept : OrderLine;
        attribute :>> targetLayer = PersistenceLayer::knowledgeGraph;
        attribute :>> rationale = "Order lines are DBR content, written with their order and held in the knowledge graph (S515 D1). Each line's preparation axis moves as the line is made.";
        attribute :>> characteristics = (DataCharacteristic::transactionalIntegrity, DataCharacteristic::highFrequencyUpdate);
    }

    part orderWorkflowPolicy : PersistencePolicy {
        doc /* Stateful process: durable execution, signal handling,
             * activity orchestration. Temporal's store is private
             * realiser storage, never a source of truth: anything with
             * meaning beyond the workflow is written to DSR through its
             * binding (H-0462). */
        ref :>> domainConcept : FulfilDrinkOrchestration::FulfilDrinkWorkflow;
        attribute :>> targetLayer = PersistenceLayer::processEngine;
        attribute :>> rationale = "Temporal's store is private realiser storage, never a source of truth; anything with meaning beyond the workflow is written to DSR through its binding (H-0462).";
        attribute :>> characteristics = (DataCharacteristic::durableExecution, DataCharacteristic::eventDriven);
    }

    part externalKnowledgePolicy : PersistencePolicy {
        doc /* Knowledge the system links to but does not own.
             * Coffee shop: supplier datasheets.
             * GSL: SPCs, BNF entries, NICE guidance. */
        ref :>> domainConcept : BusinessMetamodelGeneral::ServiceConcept::ExternalReference;
        attribute :>> targetLayer = PersistenceLayer::externalReference;
        attribute :>> rationale = "Knowledge the system links to but does not own.";
        attribute :>> characteristics = DataCharacteristic::referenceData;
    }

    // -- Stakeholder Model ------------------------------------
    //
    // Cross-domain validation: StakeholderModel instantiations for
    // a simple retail service business. Session 81.

    part localAuthorityRelationship : StakeholderRelationship {
        doc /* Local authority food safety — the primary regulatory
             * relationship for a coffee shop. */
        attribute :>> stakeholderName = "Local authority (food safety)";
        attribute :>> stakeholderDescription = "Environmental health department responsible for food safety inspections and ratings.";
        attribute :>> relationshipNature = RelationshipNature::regulatory;
        attribute :>> obligationsInward = "Sets food hygiene standards, conducts inspections, issues food hygiene ratings.";
        attribute :>> obligationsOutward = "Comply with food hygiene regulations, maintain premises standards, cooperate with inspections.";
        attribute :>> informationExchanged = "Registration details, inspection evidence (outward). Inspection reports, ratings, improvement notices (inward).";
        attribute :>> governanceArrangements = "Food business registration. Periodic unannounced inspections under the Food Hygiene Rating Scheme.";
        attribute :>> healthIndicators = "Current food hygiene rating (target: 5), time since last inspection, any outstanding improvement notices.";
        attribute :>> reviewCadence = "Inspection cycle determined by local authority — typically 6-18 months depending on risk rating.";
    }

    part landlordRelationship : StakeholderRelationship {
        attribute :>> stakeholderName = "Landlord";
        attribute :>> stakeholderDescription = "Property owner — contractual relationship governing premises use.";
        attribute :>> relationshipNature = RelationshipNature::contractual;
        attribute :>> obligationsInward = "Provides and maintains premises. Structural repairs, insurance of building.";
        attribute :>> obligationsOutward = "Pay rent, maintain interior, comply with lease terms, insure contents and liability.";
        attribute :>> informationExchanged = "Maintenance requests (outward). Lease terms, planned works, rent reviews (inward).";
        attribute :>> governanceArrangements = "Commercial lease agreement. Annual rent review.";
        attribute :>> healthIndicators = "Rent payment status, maintenance response times, lease renewal status.";
        attribute :>> reviewCadence = "Quarterly informal. Annual rent review. Lease renewal at term end.";
    }

    part deliveryPlatformPartnership : CooperativeArrangement {
        doc /* Delivery platform partnership — shared order
             * fulfilment. Neither party delivers the full
             * experience independently. */
        attribute :>> arrangementName = "Delivery platform partnership";
        attribute :>> cooperatingEntity = "Delivery platform (e.g. Deliveroo, UberEats)";
        attribute :>> sharedOutcome = "Delivery of coffee shop products to customers who order remotely — the shop prepares, the platform delivers";
        attribute :>> responsibilitySplit = "Shop: order preparation, packaging, quality control. Platform: customer interface, delivery logistics, payment processing.";
        attribute :>> protocolReference = "Platform partner agreement and order integration specification";
        attribute :>> informationSharing = "Order details and preparation status (via platform API). Delivery status and customer feedback (from platform).";
        attribute :>> disputeResolution = "Platform dispute resolution process for order issues. Escalation to account manager for systemic problems.";
        attribute :>> performanceIndicators = "Order accuracy rate, preparation time, delivery rating, customer complaints via platform.";
    }

    part coffeeBeanSupply : ExternalDependency {
        attribute :>> dependencyName = "Coffee bean supply";
        attribute :>> provider = "Specialty coffee roaster/wholesaler";
        attribute :>> dependencyDescription = "Supply of roasted coffee beans — the core input for the business's primary product.";
        attribute :>> criticality = DependencyCriticality::essential;
        attribute :>> substitutability = "Multiple specialty roasters available. Switching may change flavour profile and affect customer expectations. Blend matching possible.";
        attribute :>> contingencyPlan = "Secondary supplier relationship maintained. Emergency stock of standard blend (2 weeks). Customer communication plan for blend changes.";
        attribute :>> contractualTerms = "Monthly order with volume discount. 30-day payment terms.";
        attribute :>> supplyRisk = "Supply chain disruption (shipping, harvest failure), price volatility due to commodity market, quality inconsistency.";
    }

    part localNeighbourhood : CommunityRelationship {
        attribute :>> communityName = "Local neighbourhood";
        attribute :>> communityDescription = "Residents, workers, and visitors in the immediate area around the shop.";
        attribute :>> relationshipToService = "Constitutive — the neighbourhood provides the customer base and the shop contributes to local character and social life.";
        attribute :>> engagementMode = "Community noticeboard, local events participation, loyalty programme, regular customer relationships.";
        attribute :>> mutualBenefit = "Community gains a social gathering place and quality coffee. Shop gains loyal customer base and word-of-mouth referrals.";
        attribute :>> communityVoice = "Customer feedback, informal conversations, social media engagement, local business network meetings.";
    }

    part cafeParticipation : ParticipationModel {
        doc /* Minimal participation — customer as recipient. The
             * coffee shop has the lightest participation model of
             * all demonstrator domains. */
        attribute :>> participationName = "Counter ordering";
        attribute :>> participantRole = "Recipient — customer orders and receives, minimal co-production";
        attribute :>> participationDescription = "Customer selects from menu, places order, pays, and receives prepared drink. Participation is limited to preference expression at point of order.";
        attribute :>> informationContribution = "Order preferences (drink type, milk choice, extras). No ongoing information contribution.";
        attribute :>> decisionInvolvement = "Informed — customer chooses from available options. No shared decision-making.";
        attribute :>> selfServiceScope = "Menu browsing, order placement (counter or app). No self-service preparation.";
        attribute :>> supportRequired = "Clear menu display, allergen information, queue management.";
    }
}
